module ietf-iana-power-and-energy {
  yang-version 1.1;
  namespace "urn:ietf:params:xml:ns:yang:ietf-iana-power-and-energy";
  prefix ianaeo;

  organization "IANA";
  contact
    "        Internet Assigned Numbers Authority

     Postal: ICANN
             12025 Waterfront Drive, Suite 300
             Los Angeles, CA  90094-2536
             United States of America

     Tel:    +1 310 301 5800
     E-Mail: iana@iana.org>";

  description
    "IANA-defined identities for power and energy class.

     The latest revision of this YANG module can be obtained from
     the IANA website.

     Requests for new values should be made to IANA via
     email (iana@iana.org).

     Copyright (c) 2026 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).

     The initial version of this YANG module is part of RFC XXX;
     see the RFC itself for full legal notices.";
  reference
    "https://www.iana.org/assignments/yang-parameters";

  revision 2026-02-26 {
    description
      "Initial revision.";
    reference
      "RFC XXX: A YANG Data Model for Power and Energy monitoring and
     control of devices within or connected to communication
     networks";
  }

  identity certification-type {
    description
      "Base identity for certification types applicable to energy
       objects. This identity serves as the root for a hierarchy of
       certification types, allowing for extensibility.";

    reference
      "Industry sustainability and energy efficiency certifications";
  }

  identity energy-star {
    base certification-type;
    description
      "ENERGY STAR certification for energy efficiency.";
    reference
      "https://www.energystar.gov/";
  }

  identity c80-plus{
    base certification-type;
    description
      "80 PLUS Power Supply Certification";
    reference
      "https://www.clearesult.com/80plus/";
  }

  identity epeat {
    base certification-type;
    description
      "Electronic Product Environmental Assessment Tool ratings (Bronze/Silver/Gold).";
    reference
      "https://www.epeat.net/";
  }

  identity eu-energy-level{
    base certification-type;
    description
      "EU Energy Label: European efficiency ratings";
    reference
      "https://eprel.ec.europa.eu/screen/home";
  }

  identity cn-energy-level{
    base certification-type;
    description
      "CN Energy Label: China efficiency ratings";
    reference
      "https://www.energylabel.com.cn";
  }

  identity cqc{
    base certification-type;
    description
      "China Quality Certification for energy efficiency";
    reference
      "https://www.cqc.com.cn/";
  }

}
